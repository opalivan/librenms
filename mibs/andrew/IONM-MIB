--
-- IONM-MIB.mib
-- MIB generated by MG-SOFT Visual MIB Builder Version 3.0 Build 253
-- Monday, June 15, 2015 at 15:57:11
--

	IONM-MIB DEFINITIONS ::= BEGIN
 
		IMPORTS
			OBJECT-GROUP			
				FROM SNMPv2-CONF			
			Integer32, OBJECT-TYPE, MODULE-IDENTITY, OBJECT-IDENTITY			
				FROM SNMPv2-SMI			
			TruthValue, TEXTUAL-CONVENTION			
				FROM SNMPv2-TC			
			ionM, CTA, PositiveIntegerButNotZero, Version			
				FROM WIRELESS-INNOVATIONS-PRODUCTS-MIB;
	
	
		ionmConfiguration MODULE-IDENTITY 
			LAST-UPDATED "201506151500Z"		-- June 15, 2015 at 15:00 GMT
			ORGANIZATION 
				"Wireless Innovations"
			CONTACT-INFO 
				"Industriering 10
				86675 Buchdorf
				Germany"
			DESCRIPTION 
				"MIB for ION-M device configuration."
			REVISION "201506151500Z"		-- June 15, 2015 at 15:00 GMT
			DESCRIPTION
				"1.2.0.0
				Added:
				- objects poiTable
				- objects poiPathTable
				- objects poiPathPowerTable
				- objects poiPathThresholdTable
				- objects poiPathThresholdRangeTable
				- objects poiPathAlarmSuppressionTable
				- objects poiIfcTable"
			REVISION "201502251458Z"		-- February 25, 2015 at 14:58 GMT
			DESCRIPTION
				"1.1.0.0
				Added:
				- object identity connectivityUserData and sub objects
				- object identity userManagementAccounts and sub objects
				- object identity networkSwUpdate and sub objects"
			REVISION "201406111645Z"		-- June 11, 2014 at 16:45 GMT
			DESCRIPTION
				"1.0.0.0
				Created."
			::= { ionM 1 }
		
	
--
-- Textual conventions
--
	
		AccountGroupId ::= TEXTUAL-CONVENTION
			STATUS current
			DESCRIPTION 
				"Account Group id (Account Group No. + 1)"
			SYNTAX Integer32 (1..10)
			
		BoolOrNotSupportedOrNotAvailable ::= TEXTUAL-CONVENTION
			STATUS current
			DESCRIPTION 
				"Represents a boolean value resp. 'not supported' or 'not available'."
			SYNTAX INTEGER
				{
				notAvailable(-1),
				notSupported(0),
				true(1),
				false(2)
				}
			
	
--
-- Node definitions
--
	
		-- 1.3.6.1.4.1.331.1.2.1.6.1.1.1
		ionmCommon OBJECT-IDENTITY
			STATUS current
			DESCRIPTION 
				"Description."
			::= { ionmConfiguration 1 }
		
		-- 1.3.6.1.4.1.331.1.2.1.6.1.1.1.1
		connectivityUserData OBJECT-IDENTITY
			STATUS current
			DESCRIPTION 
				"Objects to control ION-M/-B Master Controller specific connectivity settings that are not 
				covered in WIRELESS-INNOVATIONS-PRODUCTS-MIB commonDeviceObjects.commonDeviceConnectivity"
			::= { ionmCommon 1 }
		
		-- 1.3.6.1.4.1.331.1.2.1.6.1.1.1.1.1
		customMIB OBJECT-TYPE
			SYNTAX INTEGER
				{
				none(0),
				standard(1),
				customS(2),
				customV(3),
				standardLegacyIonb(5),
				customVLegacyIonb(6)
				}
			MAX-ACCESS read-write
			STATUS current
			DESCRIPTION
				"Object that shows / controls which custom MIB is in use / to be used.
				
				#web reference: ION System>Settings>Connectivity->User Data>Custom Mib"
			::= { connectivityUserData 1 }
		
		-- 1.3.6.1.4.1.331.1.2.1.6.1.1.1.2
		userManagementAccounts OBJECT-IDENTITY
			STATUS current
			DESCRIPTION 
				"Objects to control ION-M/-B Master Controller user / account management.
				
				#web reference: ION System>Settings>User Management->Accounts"
			::= { ionmCommon 2 }
		
		-- 1.3.6.1.4.1.331.1.2.1.6.1.1.1.2.2
		accountGroupTable OBJECT-TYPE
			SYNTAX SEQUENCE OF AccountGroupEntry
			MAX-ACCESS not-accessible
			STATUS current
			DESCRIPTION
				"Table that contains the ION-M/-B Master Controller user / account groups.
				
				#web reference: ION System>Settings>User Management->Accounts:Account Groups"
			::= { userManagementAccounts 2 }
		
		-- 1.3.6.1.4.1.331.1.2.1.6.1.1.1.2.2.1
		accountGroupEntry OBJECT-TYPE
			SYNTAX AccountGroupEntry
			MAX-ACCESS not-accessible
			STATUS current
			DESCRIPTION
				"Description."
			INDEX { accountGroupId }
			::= { accountGroupTable 1 }
		
		AccountGroupEntry ::=
			SEQUENCE { 
				accountGroupId
					AccountGroupId,
				accountGroupRole
					OCTET STRING,
				accountGroupName
					OCTET STRING
			 }

		-- 1.3.6.1.4.1.331.1.2.1.6.1.1.1.2.2.1.1
		accountGroupId OBJECT-TYPE
			SYNTAX AccountGroupId
			MAX-ACCESS read-only
			STATUS current
			DESCRIPTION
				"Account Group id (Account Group No. + 1)"
			::= { accountGroupEntry 1 }
		
		-- 1.3.6.1.4.1.331.1.2.1.6.1.1.1.2.2.1.2
		accountGroupRole OBJECT-TYPE
			SYNTAX OCTET STRING
			MAX-ACCESS read-only
			STATUS current
			DESCRIPTION
				"Account Group Role."
			::= { accountGroupEntry 2 }
		
		-- 1.3.6.1.4.1.331.1.2.1.6.1.1.1.2.2.1.3
		accountGroupName OBJECT-TYPE
			SYNTAX OCTET STRING (SIZE (1..20))
			MAX-ACCESS read-only
			STATUS current
			DESCRIPTION
				"Account Group Name."
			::= { accountGroupEntry 3 }
		
		-- 1.3.6.1.4.1.331.1.2.1.6.1.1.1.2.3
		accountTable OBJECT-TYPE
			SYNTAX SEQUENCE OF AccountEntry
			MAX-ACCESS not-accessible
			STATUS current
			DESCRIPTION
				"Table that contains ION-M/-B Master Controller users / accounts per user / account group.
				
				#web reference: ION System>Settings>User Management->Accounts:Account Groups>Accounts"
			::= { userManagementAccounts 3 }
		
		-- 1.3.6.1.4.1.331.1.2.1.6.1.1.1.2.3.1
		accountEntry OBJECT-TYPE
			SYNTAX AccountEntry
			MAX-ACCESS not-accessible
			STATUS current
			DESCRIPTION
				"Description."
			INDEX { accountGroupIdref, accountId }
			::= { accountTable 1 }
		
		AccountEntry ::=
			SEQUENCE { 
				accountGroupIdref
					AccountGroupId,
				accountId
					PositiveIntegerButNotZero,
				accountName
					OCTET STRING,
				accountPwAct
					OCTET STRING,
				accountPwNew
					OCTET STRING
			 }

		-- 1.3.6.1.4.1.331.1.2.1.6.1.1.1.2.3.1.1
		accountGroupIdref OBJECT-TYPE
			SYNTAX AccountGroupId
			MAX-ACCESS read-only
			STATUS current
			DESCRIPTION
				"Account Group id (Account Group No. + 1)"
			::= { accountEntry 1 }
		
		-- 1.3.6.1.4.1.331.1.2.1.6.1.1.1.2.3.1.2
		accountId OBJECT-TYPE
			SYNTAX PositiveIntegerButNotZero
			MAX-ACCESS read-only
			STATUS current
			DESCRIPTION
				"Account id (Account No.)"
			::= { accountEntry 2 }
		
		-- 1.3.6.1.4.1.331.1.2.1.6.1.1.1.2.3.1.3
		accountName OBJECT-TYPE
			SYNTAX OCTET STRING (SIZE (1..20))
			MAX-ACCESS read-only
			STATUS current
			DESCRIPTION
				"Account Name."
			::= { accountEntry 3 }
		
		-- 1.3.6.1.4.1.331.1.2.1.6.1.1.1.2.3.1.4
		accountPwAct OBJECT-TYPE
			SYNTAX OCTET STRING (SIZE (0..8))
			MAX-ACCESS read-write
			STATUS current
			DESCRIPTION
				"Change account password: Account actual password. 
				
				Needs to be set in advance to the new account password (accountPwNew).
				
				Reading this object returns 8 asterisk character '********'."
			::= { accountEntry 4 }
		
		-- 1.3.6.1.4.1.331.1.2.1.6.1.1.1.2.3.1.5
		accountPwNew OBJECT-TYPE
			SYNTAX OCTET STRING (SIZE (0..8))
			MAX-ACCESS read-write
			STATUS current
			DESCRIPTION
				"Change account password: New password.
				
				In case the previously set of the actual password (accountPwAct) 
				does not match the actual effective password, 
				error inconsistentValue gets responded and the new password will not be applied.
				
				Reading this object returns 8 asterisk character '********'."
			::= { accountEntry 5 }
		
		-- 1.3.6.1.4.1.331.1.2.1.6.1.1.1.3
		networkSwUpdate OBJECT-IDENTITY
			STATUS current
			DESCRIPTION 
				"Objects to control the SW update process of ION-M optical network components.
				
				Workflow in case nwSwUpdateMode = automatic:
				- The update of the network components is started automatically right after the 
				  Master Controller was successfully updated via the WIRELESS-INNOVATIONS-PRODUCTS-MIB.
				- All state transitions idle->preparation->preparationDone->start->inProgress->done 
				  are performed automatically by the Agent.
				
				Workflow in case nwSwUpdateMode = manual:
				- Manager may set nwSwUpdateExclusiveTask according his needs
				- Manager sets nwSwUpdateState = preparation,
				  upon this the Agent initializes and fills the nwSwTable.
				  Once this is done, the Agent sets nwSwUpdateState = preparationDone.
				- Manager may modify nwSwTable.nwSwSelect4Update
				- Manager sets nwSwUpdateState = start 
				  in order to start the SW update process of the ION-M optical network components, 
				  upon this the Agent sets nwSwUpdateState = inProgress and starts the update process.
				- Manager may monitor the progress via nwSwCurrentPercentage and nwSwOverallPercentage
				  or cancel it by setting state back to idle.
				- Once the SW update is finished, the Agent provides the SW update results in 
				  nwSwTable.nwSwResultOk and nwSwResultString plus
				  nwSwOverallResultOk and nwSwOverallResultString 
				  and finally the Agent sets nwSwUpdateState = done
				- Manager may check the SW update results via nwSwOverallResultOk and nwSwOverallResultString, 
				  additionally per component via nwSwTable.nwSwResultOk and nwSwResultString"
			::= { ionmCommon 3 }
		
		-- 1.3.6.1.4.1.331.1.2.1.6.1.1.1.3.1
		nwSwUpdateMode OBJECT-TYPE
			SYNTAX INTEGER
				{
				automatic(1),
				manual(2)
				}
			MAX-ACCESS read-write
			STATUS current
			DESCRIPTION
				"Object to control the mode of the SW update of the ION-M optical network components.
				
				manual (default value if not explicitly set):
				The update of the network components needs to be started explicitly via SW Update 
				state machine (nwSwUpdateState).
				
				automatic:
				The update of the network components is started automatically right after the 
				Master Controller was successfully updated via the WIRELESS-INNOVATIONS-PRODUCTS-MIB.
				
				
				SET is only allowed in state idle."
			DEFVAL { manual }
			::= { networkSwUpdate 1 }
		
		-- 1.3.6.1.4.1.331.1.2.1.6.1.1.1.3.2
		nwSwUpdateExclusiveTask OBJECT-TYPE
			SYNTAX TruthValue
			MAX-ACCESS read-write
			STATUS current
			DESCRIPTION
				"Object to control whether the SW update of the ION-M optical network components runs as 
				exclusive Master Controller task or not.
				
				false (default value if not explicitly set):
				The update of the network components runs parallel to the Master Controller alarm and 
				auto-levelling polling. I.e. alarming and auto-levelling is assured.
				
				true:
				Master Controller alarm and auto-levelling polling is suspended for the period of time the 
				SW update of the ION-M optical network components lasts.
				
				Setting to true increases the update performance but alarming and auto-levelling is not 
				working during SW update of the network components.
				
				
				SET is only allowed in state idle."
			DEFVAL { false }
			::= { networkSwUpdate 2 }
		
		-- 1.3.6.1.4.1.331.1.2.1.6.1.1.1.3.3
		nwSwUpdateState OBJECT-TYPE
			SYNTAX INTEGER
				{
				idle(1),
				preparation(2),
				preparationDone(3),
				start(4),
				inProgress(5),
				done(6)
				}
			MAX-ACCESS read-write
			STATUS current
			DESCRIPTION
				"State of the SW update process of the ION-M optical network components.
				
				idle:
				State idle indicates that no SW update of ION-M optical network components is active.
				Initial state.
				State transition back to idle has to be possible out of states inProgress and idle.
				Upon this, the Agent cancels a possibly running SW update process and resets the 
				following objects to the default values:
				nwSwUpdateMode = manual
				nwSwUpdateExclusiveTask = false
				nwSwTable is cleared (table empty)
				nwSwSelectAll4Update = 0
				nwSwCurrentInProgress set to empty string
				nwSwCurrentPercentage = 0
				nwSwOverallPercentage = 0
				nwSwOverallResultOk = false
				nwSwOverallResultString set to empty string
				
				
				preparation:
				SW update of ION-M optical network preparation state.
				In manual mode state set by Manager, in automatic mode by Agent.
				nwSwTable gets initialized and will be filled by the Agent.
				
				preparationDone:
				SW update of ION-M optical network preparation finished state.
				State always set by Agent.
				nwSwTable is ready filled, nwSwTable.nwSwSelect4Update is preselected for all sub 
				components where nwSwComponentActVersion is not equal with nwSwComponentNewVersion.
				
				start:
				State transition to start starts the SW update process of the ION-M optical network components.
				In manual mode state set by Manager, in automatic mode by Agent.
				
				inProgress:
				SW update process of the ION-M optical network components is running.
				State always set by Agent.
				Progress can be monitored by Manager via nwSwCurrentPercentage and nwSwOverallPercentage or 
				cancelled by setting state back to idle.
				
				done:
				SW update process of the ION-M optical network components is finished. 
				State always set by Agent.
				Results are reflected in nwSwTable.nwSwResultOk and nwSwResultString plus
				nwSwOverallResultOk and nwSwOverallResultString."
			::= { networkSwUpdate 3 }
		
		-- 1.3.6.1.4.1.331.1.2.1.6.1.1.1.3.4
		nwSwTable OBJECT-TYPE
			SYNTAX SEQUENCE OF NwSwEntry
			MAX-ACCESS not-accessible
			STATUS current
			DESCRIPTION
				"Table that lists all ION-M optical network active sub components with all 
				SW update relevant data.
				
				Table gets filled when entering state preparation."
			::= { networkSwUpdate 4 }
		
		-- 1.3.6.1.4.1.331.1.2.1.6.1.1.1.3.4.1
		nwSwEntry OBJECT-TYPE
			SYNTAX NwSwEntry
			MAX-ACCESS not-accessible
			STATUS current
			DESCRIPTION
				"Description."
			INDEX { nwSwSubComponentCTA, nwSwSubComponent }
			::= { nwSwTable 1 }
		
		NwSwEntry ::=
			SEQUENCE { 
				nwSwSubComponentCTA
					CTA,
				nwSwSubComponent
					OCTET STRING,
				nwSwComponentActVersion
					Version,
				nwSwComponentNewVersion
					Version,
				nwSwComponentFilename
					OCTET STRING,
				nwSwSelect4Update
					TruthValue,
				nwSwResultOk
					INTEGER,
				nwSwResultString
					OCTET STRING
			 }

		-- 1.3.6.1.4.1.331.1.2.1.6.1.1.1.3.4.1.1
		nwSwSubComponentCTA OBJECT-TYPE
			SYNTAX CTA
			MAX-ACCESS read-only
			STATUS current
			DESCRIPTION
				"Common Topology Address of the component."
			::= { nwSwEntry 1 }
		
		-- 1.3.6.1.4.1.331.1.2.1.6.1.1.1.3.4.1.2
		nwSwSubComponent OBJECT-TYPE
			SYNTAX OCTET STRING
			MAX-ACCESS read-only
			STATUS current
			DESCRIPTION
				"Sub component name (e.g. Controller, Display, FCM, ...)."
			::= { nwSwEntry 2 }
		
		-- 1.3.6.1.4.1.331.1.2.1.6.1.1.1.3.4.1.3
		nwSwComponentActVersion OBJECT-TYPE
			SYNTAX Version
			MAX-ACCESS read-only
			STATUS current
			DESCRIPTION
				"Actual running sub component SW version."
			::= { nwSwEntry 3 }
		
		-- 1.3.6.1.4.1.331.1.2.1.6.1.1.1.3.4.1.4
		nwSwComponentNewVersion OBJECT-TYPE
			SYNTAX Version
			MAX-ACCESS read-only
			STATUS current
			DESCRIPTION
				"New SW version for the sub component contained in the actual running Master 
				Controller / ION-M system SW package."
			::= { nwSwEntry 4 }
		
		-- 1.3.6.1.4.1.331.1.2.1.6.1.1.1.3.4.1.5
		nwSwComponentFilename OBJECT-TYPE
			SYNTAX OCTET STRING
			MAX-ACCESS read-only
			STATUS current
			DESCRIPTION
				"File name of SW binary file."
			::= { nwSwEntry 5 }
		
		-- 1.3.6.1.4.1.331.1.2.1.6.1.1.1.3.4.1.6
		nwSwSelect4Update OBJECT-TYPE
			SYNTAX TruthValue
			MAX-ACCESS read-write
			STATUS current
			DESCRIPTION
				"Object that shows / controls whether the sub component should be updated 
				to the new SW version or not.
				
				SET is only allowed in state preparation."
			::= { nwSwEntry 6 }
		
		-- 1.3.6.1.4.1.331.1.2.1.6.1.1.1.3.4.1.7
		nwSwResultOk OBJECT-TYPE
			SYNTAX INTEGER
				{
				notApplicable(0),
				true(1),
				false(2)
				}
			MAX-ACCESS read-only
			STATUS current
			DESCRIPTION
				"SW update result for the sub component. Indicates whether update was successful or not.
				
				GET value is only valid in state done."
			::= { nwSwEntry 7 }
		
		-- 1.3.6.1.4.1.331.1.2.1.6.1.1.1.3.4.1.8
		nwSwResultString OBJECT-TYPE
			SYNTAX OCTET STRING
			MAX-ACCESS read-only
			STATUS current
			DESCRIPTION
				"Detailed description of actual SW update result for the sub component.
				
				Syntax: 'E'(rror)|'W'(arning)|'I'(nfo)+': <Result text>' or empty string.
				
				Possible result strings (examples):
				- 'I: Sub component successfully updated from <nwSwComponentActVersion> to <nwSwComponentNewVersion>'
				- 'W: Sub component not selected for update'
				- 'E: Communication error during SW update'
				
				GET value is only valid in state done."
			::= { nwSwEntry 8 }
		
		-- 1.3.6.1.4.1.331.1.2.1.6.1.1.1.3.5
		nwSwSelectAll4Update OBJECT-TYPE
			SYNTAX INTEGER
				{
				both(0),
				true(1),
				false(2)
				}
			MAX-ACCESS read-write
			STATUS current
			DESCRIPTION
				"Object that shows resp. controls whether all components listed in the nwSwTable 
				are included in the SW update process of the ION-M optical network components or not.
				
				SET is only allowed in state preparation.
				GET value is only valid in state preparationDone, inProgress or done.
				
				SET to both(0) is not allowed and will result in error wrongValue.
				SET to true(1) selects all components for update.
				SET to false(2) de-selects all components for update.
				
				GET returns both(0) in case some components are selected and some are de-selected for update.
				GET returns true(1) in case all components are selected for update.
				GET returns false(2) in case all components are de-selected for update."
			::= { networkSwUpdate 5 }
		
		-- 1.3.6.1.4.1.331.1.2.1.6.1.1.1.3.6
		nwSwCurrentInProgress OBJECT-TYPE
			SYNTAX OCTET STRING
			MAX-ACCESS read-only
			STATUS current
			DESCRIPTION
				"This object indicates on which sub component at which topology address 
				a SW update is currently in progress.
				Format:
				<CTA> (<SubComponent>)"
			::= { networkSwUpdate 6 }
		
		-- 1.3.6.1.4.1.331.1.2.1.6.1.1.1.3.7
		nwSwCurrentPercentage OBJECT-TYPE
			SYNTAX Integer32 (0..100)
			MAX-ACCESS read-only
			STATUS current
			DESCRIPTION
				"This object indicates the percentage of the SW update process 
				for the corresponding sub component which is already done.
				
				GET value is only valid in state inProgress or done."
			::= { networkSwUpdate 7 }
		
		-- 1.3.6.1.4.1.331.1.2.1.6.1.1.1.3.8
		nwSwOverallPercentage OBJECT-TYPE
			SYNTAX Integer32 (0..100)
			MAX-ACCESS read-only
			STATUS current
			DESCRIPTION
				"This object indicates the percentage of the overall SW update process of the 
				ION-M optical network components which is already done.
				
				GET value is only valid in state inProgress or done."
			::= { networkSwUpdate 8 }
		
		-- 1.3.6.1.4.1.331.1.2.1.6.1.1.1.3.9
		nwSwOverallResultOk OBJECT-TYPE
			SYNTAX TruthValue
			MAX-ACCESS read-only
			STATUS current
			DESCRIPTION
				"SW update result for the overall SW update process of the ION-M optical network 
				components. Indicates whether update was successful or not.
				
				GET value is only valid in state preparationDone or done."
			::= { networkSwUpdate 9 }
		
		-- 1.3.6.1.4.1.331.1.2.1.6.1.1.1.3.10
		nwSwOverallResultString OBJECT-TYPE
			SYNTAX OCTET STRING
			MAX-ACCESS read-only
			STATUS current
			DESCRIPTION
				"Detailed description of actual SW update result for the overall SW update process 
				of the ION-M optical network components.
				
				Syntax: 'E'(rror)|'W'(arning)|'I'(nfo)+': <Result text>' or empty string.
				
				Possible result strings (examples):
				- 'I: All ION-M optical network components successfully updated'
				- 'E: SW package error: TOC file error'
				
				GET value is only valid in state preparationDone or done."
			::= { networkSwUpdate 10 }
		
		-- 1.3.6.1.4.1.331.1.2.1.6.1.1.2
		ionmLocal OBJECT-IDENTITY
			STATUS current
			DESCRIPTION 
				"Description."
			::= { ionmConfiguration 2 }
		
		-- 1.3.6.1.4.1.331.1.2.1.6.1.1.2.1
		muOtrxTable OBJECT-TYPE
			SYNTAX SEQUENCE OF MuOtrxEntry
			MAX-ACCESS not-accessible
			STATUS current
			DESCRIPTION
				"Description."
			::= { ionmLocal 1 }
		
		-- 1.3.6.1.4.1.331.1.2.1.6.1.1.2.1.1
		muOtrxEntry OBJECT-TYPE
			SYNTAX MuOtrxEntry
			MAX-ACCESS not-accessible
			STATUS current
			DESCRIPTION
				"Description."
			INDEX { muOtrxCTA }
			::= { muOtrxTable 1 }
		
		MuOtrxEntry ::=
			SEQUENCE { 
				muOtrxCTA
					CTA,
				muOtrxReboot
					TruthValue,
				muOtrxTempOptic
					OCTET STRING
			 }

		-- 1.3.6.1.4.1.331.1.2.1.6.1.1.2.1.1.1
		muOtrxCTA OBJECT-TYPE
			SYNTAX CTA
			MAX-ACCESS read-only
			STATUS current
			DESCRIPTION
				"Description."
			::= { muOtrxEntry 1 }
		
		-- 1.3.6.1.4.1.331.1.2.1.6.1.1.2.1.1.2
		muOtrxReboot OBJECT-TYPE
			SYNTAX TruthValue
			MAX-ACCESS read-write
			STATUS current
			DESCRIPTION
				"Description."
			::= { muOtrxEntry 2 }
		
		-- 1.3.6.1.4.1.331.1.2.1.6.1.1.2.1.1.3
		muOtrxTempOptic OBJECT-TYPE
			SYNTAX OCTET STRING
			MAX-ACCESS read-only
			STATUS current
			DESCRIPTION
				"String representation of float value."
			::= { muOtrxEntry 3 }
		
		-- 1.3.6.1.4.1.331.1.2.1.6.1.1.2.2
		poiTable OBJECT-TYPE
			SYNTAX SEQUENCE OF PoiEntry
			MAX-ACCESS not-accessible
			STATUS current
			DESCRIPTION
				"This table lists the identification settings for all i-POI modules."
			::= { ionmLocal 2 }
		
		-- 1.3.6.1.4.1.331.1.2.1.6.1.1.2.2.1
		poiEntry OBJECT-TYPE
			SYNTAX PoiEntry
			MAX-ACCESS not-accessible
			STATUS current
			DESCRIPTION
				"Description."
			INDEX { poiCTA }
			::= { poiTable 1 }
		
		PoiEntry ::=
			SEQUENCE { 
				poiCTA
					CTA,
				poiName
					OCTET STRING,
				poiLocation
					OCTET STRING,
				poiSectorID
					OCTET STRING,
				poiFrequency
					OCTET STRING,
				poiStandard
					OCTET STRING,
				poiUserAssignment
					OCTET STRING,
				poiTemp
					Integer32
			 }

		-- 1.3.6.1.4.1.331.1.2.1.6.1.1.2.2.1.1
		poiCTA OBJECT-TYPE
			SYNTAX CTA
			MAX-ACCESS read-only
			STATUS current
			DESCRIPTION
				"Topology address of the POI module.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiEntry 1 }
		
		-- 1.3.6.1.4.1.331.1.2.1.6.1.1.2.2.1.2
		poiName OBJECT-TYPE
			SYNTAX OCTET STRING
			MAX-ACCESS read-only
			STATUS current
			DESCRIPTION
				"Associated name of the referenced POI module.
				
				Note well:
				- 'notAvailable' may be responded in case the value is temporary not available (try later).
				- 'notSupported' indicates that the object is not supported by the referenced POI."
			::= { poiEntry 2 }
		
		-- 1.3.6.1.4.1.331.1.2.1.6.1.1.2.2.1.3
		poiLocation OBJECT-TYPE
			SYNTAX OCTET STRING
			MAX-ACCESS read-only
			STATUS current
			DESCRIPTION
				"Associated location of the referenced POI module.
				
				Note well:
				- 'notAvailable' may be responded in case the value is temporary not available (try later).
				- 'notSupported' indicates that the object is not supported by the referenced POI."
			::= { poiEntry 3 }
		
		-- 1.3.6.1.4.1.331.1.2.1.6.1.1.2.2.1.4
		poiSectorID OBJECT-TYPE
			SYNTAX OCTET STRING
			MAX-ACCESS read-only
			STATUS current
			DESCRIPTION
				"Associated sector ID for the referenced POI module.
				
				Note well:
				- 'notAvailable' may be responded in case the value is temporary not available (try later).
				- 'notSupported' indicates that the object is not supported by the referenced POI."
			::= { poiEntry 4 }
		
		-- 1.3.6.1.4.1.331.1.2.1.6.1.1.2.2.1.5
		poiFrequency OBJECT-TYPE
			SYNTAX OCTET STRING
			MAX-ACCESS read-only
			STATUS current
			DESCRIPTION
				"Associated frequency in MHz for the referenced POI module.
				
				String representation of a float value.
				
				Note well:
				- 'notAvailable' may be responded in case the value is temporary not available (try later).
				- 'notSupported' indicates that the object is not supported by the referenced POI."
			::= { poiEntry 5 }
		
		-- 1.3.6.1.4.1.331.1.2.1.6.1.1.2.2.1.6
		poiStandard OBJECT-TYPE
			SYNTAX OCTET STRING
			MAX-ACCESS read-only
			STATUS current
			DESCRIPTION
				"Associated standard for the referenced POI module.
				
				Note well:
				- 'notAvailable' may be responded in case the value is temporary not available (try later).
				- 'notSupported' indicates that the object is not supported by the referenced POI."
			::= { poiEntry 6 }
		
		-- 1.3.6.1.4.1.331.1.2.1.6.1.1.2.2.1.7
		poiUserAssignment OBJECT-TYPE
			SYNTAX OCTET STRING
			MAX-ACCESS read-only
			STATUS current
			DESCRIPTION
				"Associated user account group for the referenced POI module.
				
				Note well:
				- 'allAccounts' denotes all user account groups.
				- 'notAvailable' may be responded in case the value is temporary not available (try later).
				- 'notSupported' indicates that the object is not supported by the referenced POI."
			::= { poiEntry 7 }
		
		-- 1.3.6.1.4.1.331.1.2.1.6.1.1.2.2.1.8
		poiTemp OBJECT-TYPE
			SYNTAX Integer32
			MAX-ACCESS read-only
			STATUS current
			DESCRIPTION
				"POI module temperature in degree Celsius.
				
				Note well:
				- MIN(Integer32) may be responded in case the value is temporary not available (try later).
				- MAX(Integer32) indicates that the object is not supported by the referenced POI."
			::= { poiEntry 8 }
		
		-- 1.3.6.1.4.1.331.1.2.1.6.1.1.2.3
		poiPathTable OBJECT-TYPE
			SYNTAX SEQUENCE OF PoiPathEntry
			MAX-ACCESS not-accessible
			STATUS current
			DESCRIPTION
				"This table lists the path settings for all i-POI modules."
			::= { ionmLocal 3 }
		
		-- 1.3.6.1.4.1.331.1.2.1.6.1.1.2.3.1
		poiPathEntry OBJECT-TYPE
			SYNTAX PoiPathEntry
			MAX-ACCESS not-accessible
			STATUS current
			DESCRIPTION
				"Description."
			INDEX { poiPathPoiCTA, poiPathIndex }
			::= { poiPathTable 1 }
		
		PoiPathEntry ::=
			SEQUENCE { 
				poiPathPoiCTA
					CTA,
				poiPathIndex
					PositiveIntegerButNotZero,
				poiPathLabel
					OCTET STRING,
				poiPathIsActive
					INTEGER,
				poiPathAlcEnabled
					BoolOrNotSupportedOrNotAvailable
			 }

		-- 1.3.6.1.4.1.331.1.2.1.6.1.1.2.3.1.1
		poiPathPoiCTA OBJECT-TYPE
			SYNTAX CTA
			MAX-ACCESS read-only
			STATUS current
			DESCRIPTION
				"Topology address of the corresponding POI module to which the POI path belongs to.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiPathEntry 1 }
		
		-- 1.3.6.1.4.1.331.1.2.1.6.1.1.2.3.1.2
		poiPathIndex OBJECT-TYPE
			SYNTAX PositiveIntegerButNotZero
			MAX-ACCESS read-only
			STATUS current
			DESCRIPTION
				"Continuous POI path index."
			::= { poiPathEntry 2 }
		
		-- 1.3.6.1.4.1.331.1.2.1.6.1.1.2.3.1.3
		poiPathLabel OBJECT-TYPE
			SYNTAX OCTET STRING
			MAX-ACCESS read-only
			STATUS current
			DESCRIPTION
				"POI path identification name."
			::= { poiPathEntry 3 }
		
		-- 1.3.6.1.4.1.331.1.2.1.6.1.1.2.3.1.4
		poiPathIsActive OBJECT-TYPE
			SYNTAX INTEGER
				{
				notAvailable(-1),
				notSupported(0),
				active(1),
				inactive(2)
				}
			MAX-ACCESS read-write
			STATUS current
			DESCRIPTION
				"Path active status. 
				
				Note well:
				- Changing the path status (active to inactive or vice versa) may last up to 10 seconds.
				- notAvailable(-1) may be responded in case the value is temporary not available (try later).
				- notSupported(0) indicates that the object is not supported by the referenced POI type resp. POI path type.
				- Allowed values for SET are just active(1) or inactive(2)"
			::= { poiPathEntry 4 }
		
		-- 1.3.6.1.4.1.331.1.2.1.6.1.1.2.3.1.5
		poiPathAlcEnabled OBJECT-TYPE
			SYNTAX BoolOrNotSupportedOrNotAvailable
			MAX-ACCESS read-write
			STATUS current
			DESCRIPTION
				"ALC enabled status.
				
				Note well:
				- notAvailable(-1) may be responded in case the value is temporary not available (try later).
				- notSupported(0) indicates that the object is not supported by the referenced POI type resp. POI path type.
				- Allowed values for SET are just true(1) or false(2)"
			::= { poiPathEntry 5 }
		
		-- 1.3.6.1.4.1.331.1.2.1.6.1.1.2.4
		poiPathPowerTable OBJECT-TYPE
			SYNTAX SEQUENCE OF PoiPathPowerEntry
			MAX-ACCESS not-accessible
			STATUS current
			DESCRIPTION
				"Description."
			::= { ionmLocal 4 }
		
		-- 1.3.6.1.4.1.331.1.2.1.6.1.1.2.4.1
		poiPathPowerEntry OBJECT-TYPE
			SYNTAX PoiPathPowerEntry
			MAX-ACCESS not-accessible
			STATUS current
			DESCRIPTION
				"Description."
			INDEX { poiPathPowerPoiCTA, poiPathPowerIndexRef }
			::= { poiPathPowerTable 1 }
		
		PoiPathPowerEntry ::=
			SEQUENCE { 
				poiPathPowerPoiCTA
					CTA,
				poiPathPowerIndexRef
					PositiveIntegerButNotZero,
				poiPathPowerInput
					OCTET STRING,
				poiPathPowerAttenuation
					OCTET STRING,
				poiPathPowerOutput
					OCTET STRING
			 }

		-- 1.3.6.1.4.1.331.1.2.1.6.1.1.2.4.1.1
		poiPathPowerPoiCTA OBJECT-TYPE
			SYNTAX CTA
			MAX-ACCESS read-only
			STATUS current
			DESCRIPTION
				"Topology address of the corresponding POI module to which the POI path belongs to.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiPathPowerEntry 1 }
		
		-- 1.3.6.1.4.1.331.1.2.1.6.1.1.2.4.1.2
		poiPathPowerIndexRef OBJECT-TYPE
			SYNTAX PositiveIntegerButNotZero
			MAX-ACCESS read-only
			STATUS current
			DESCRIPTION
				"Referenced POI path index."
			::= { poiPathPowerEntry 2 }
		
		-- 1.3.6.1.4.1.331.1.2.1.6.1.1.2.4.1.3
		poiPathPowerInput OBJECT-TYPE
			SYNTAX OCTET STRING
			MAX-ACCESS read-only
			STATUS current
			DESCRIPTION
				"POI module input power of the referenced path in dBm. 
				
				String representation of a float value. 
				The string may optionally start with a '<' or '>' character. In this 
				cases it means that the actual value is lower or greater than the value 
				following this special character.
				
				Note well:
				- 'notAvailable' may be responded in case the value is temporary not available (try later).
				- 'notSupported' indicates that the object is not supported by the referenced POI type resp. POI path type."
			::= { poiPathPowerEntry 3 }
		
		-- 1.3.6.1.4.1.331.1.2.1.6.1.1.2.4.1.4
		poiPathPowerAttenuation OBJECT-TYPE
			SYNTAX OCTET STRING
			MAX-ACCESS read-write
			STATUS current
			DESCRIPTION
				"POI module internal attenuation of the referenced path in dB. 
				
				String representation of a float value.
				
				Note well:
				- 'notAvailable' may be responded in case the value is temporary not available (try later).
				- 'notSupported' indicates that the object is not supported by the referenced POI type resp. POI path type.
				- Allowed values for SET see poiPathAttenuationRange"
			::= { poiPathPowerEntry 4 }
		
		-- 1.3.6.1.4.1.331.1.2.1.6.1.1.2.4.1.5
		poiPathPowerOutput OBJECT-TYPE
			SYNTAX OCTET STRING
			MAX-ACCESS read-only
			STATUS current
			DESCRIPTION
				"POI module output power of the referenced path in dBm. 
				
				String representation of a float value. 
				The string may optionally start with a '<' or '>' character. In this 
				cases it means that the actual value is lower or greater than the value 
				following this special character.
				
				Note well:
				- 'notAvailable' may be responded in case the value is temporary not available (try later).
				- 'notSupported' indicates that the object is not supported by the referenced POI type resp. POI path type."
			::= { poiPathPowerEntry 5 }
		
		-- 1.3.6.1.4.1.331.1.2.1.6.1.1.2.5
		poiPathThresholdTable OBJECT-TYPE
			SYNTAX SEQUENCE OF PoiPathThresholdEntry
			MAX-ACCESS not-accessible
			STATUS current
			DESCRIPTION
				"Description."
			::= { ionmLocal 5 }
		
		-- 1.3.6.1.4.1.331.1.2.1.6.1.1.2.5.1
		poiPathThresholdEntry OBJECT-TYPE
			SYNTAX PoiPathThresholdEntry
			MAX-ACCESS not-accessible
			STATUS current
			DESCRIPTION
				"Description."
			INDEX { poiPathThresholdPoiCTA, poiPathThresholdIndexRef }
			::= { poiPathThresholdTable 1 }
		
		PoiPathThresholdEntry ::=
			SEQUENCE { 
				poiPathThresholdPoiCTA
					CTA,
				poiPathThresholdIndexRef
					PositiveIntegerButNotZero,
				poiPathThresholdHipAr
					OCTET STRING,
				poiPathThresholdALC
					OCTET STRING,
				poiPathThresholdLipAr
					OCTET STRING,
				poiPathThresholdLipAc
					OCTET STRING
			 }

		-- 1.3.6.1.4.1.331.1.2.1.6.1.1.2.5.1.1
		poiPathThresholdPoiCTA OBJECT-TYPE
			SYNTAX CTA
			MAX-ACCESS read-only
			STATUS current
			DESCRIPTION
				"Topology address of the corresponding POI module to which the POI path belongs to.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiPathThresholdEntry 1 }
		
		-- 1.3.6.1.4.1.331.1.2.1.6.1.1.2.5.1.2
		poiPathThresholdIndexRef OBJECT-TYPE
			SYNTAX PositiveIntegerButNotZero
			MAX-ACCESS read-only
			STATUS current
			DESCRIPTION
				"Referenced POI path index."
			::= { poiPathThresholdEntry 2 }
		
		-- 1.3.6.1.4.1.331.1.2.1.6.1.1.2.5.1.3
		poiPathThresholdHipAr OBJECT-TYPE
			SYNTAX OCTET STRING
			MAX-ACCESS read-write
			STATUS current
			DESCRIPTION
				"High Input Power Alarm Raise Threshold for the referenced path in dBm. 
				 
				String representation of float value.
				
				Note well:
				- 'notAvailable' may be responded in case the value is temporary not available (try later).
				- 'notSupported' indicates that the object is not supported by the referenced POI type resp. POI path type.
				- Allowed values for SET see poiPathThresholdRangeHipAr resp. SET is not allowed at all 
				  in case 'notSupported' was previously responded for the referenced path."
			::= { poiPathThresholdEntry 3 }
		
		-- 1.3.6.1.4.1.331.1.2.1.6.1.1.2.5.1.4
		poiPathThresholdALC OBJECT-TYPE
			SYNTAX OCTET STRING
			MAX-ACCESS read-write
			STATUS current
			DESCRIPTION
				"ALC threshold (==High Input Power Alarm Clear Threshold) of the referenced path in dBm. 
				
				String representation of float value.
				
				Note well:
				- 'notAvailable' may be responded in case the value is temporary not available (try later).
				- 'notSupported' indicates that the object is not supported by the referenced POI type resp. POI path type.
				- Allowed values for SET see poiPathThresholdRangeALC resp. SET is not allowed at all 
				  in case 'notSupported' was previously responded for the referenced path."
			::= { poiPathThresholdEntry 4 }
		
		-- 1.3.6.1.4.1.331.1.2.1.6.1.1.2.5.1.5
		poiPathThresholdLipAr OBJECT-TYPE
			SYNTAX OCTET STRING
			MAX-ACCESS read-write
			STATUS current
			DESCRIPTION
				"Low Input Power Alarm Raise Threshold for the referenced path in dBm. 
				 
				String representation of float value.
				
				Note well:
				- 'notAvailable' may be responded in case the value is temporary not available (try later).
				- 'notSupported' indicates that the object is not supported by the referenced POI type resp. POI path type.
				- Allowed values for SET see poiPathThresholdRangeLipAr resp. SET is not allowed at all 
				  in case 'notSupported' was previously responded for the referenced path."
			::= { poiPathThresholdEntry 5 }
		
		-- 1.3.6.1.4.1.331.1.2.1.6.1.1.2.5.1.6
		poiPathThresholdLipAc OBJECT-TYPE
			SYNTAX OCTET STRING
			MAX-ACCESS read-write
			STATUS current
			DESCRIPTION
				"Low Input Power Alarm Clear Threshold for the referenced path in dBm. 
				 
				String representation of float value.
				
				Note well:
				- 'notAvailable' may be responded in case the value is temporary not available (try later).
				- 'notSupported' indicates that the object is not supported by the referenced POI type resp. POI path type.
				- Allowed values for SET see poiPathThresholdRangeLipAc resp. SET is not allowed at all 
				  in case 'notSupported' was previously responded for the referenced path."
			::= { poiPathThresholdEntry 6 }
		
		-- 1.3.6.1.4.1.331.1.2.1.6.1.1.2.6
		poiPathThresholdRangeTable OBJECT-TYPE
			SYNTAX SEQUENCE OF PoiPathThresholdRangeEntry
			MAX-ACCESS not-accessible
			STATUS current
			DESCRIPTION
				"Description."
			::= { ionmLocal 6 }
		
		-- 1.3.6.1.4.1.331.1.2.1.6.1.1.2.6.1
		poiPathThresholdRangeEntry OBJECT-TYPE
			SYNTAX PoiPathThresholdRangeEntry
			MAX-ACCESS not-accessible
			STATUS current
			DESCRIPTION
				"Description."
			INDEX { poiPathThresholdRangePoiCTA, poiPathThresholdRangeIndexRef }
			::= { poiPathThresholdRangeTable 1 }
		
		PoiPathThresholdRangeEntry ::=
			SEQUENCE { 
				poiPathThresholdRangePoiCTA
					CTA,
				poiPathThresholdRangeIndexRef
					PositiveIntegerButNotZero,
				poiPathThresholdRangeAttenuation
					OCTET STRING,
				poiPathThresholdRangeHipAr
					OCTET STRING,
				poiPathThresholdRangeALC
					OCTET STRING,
				poiPathThresholdRangeLipAr
					OCTET STRING,
				poiPathThresholdRangeLipAc
					OCTET STRING
			 }

		-- 1.3.6.1.4.1.331.1.2.1.6.1.1.2.6.1.1
		poiPathThresholdRangePoiCTA OBJECT-TYPE
			SYNTAX CTA
			MAX-ACCESS read-only
			STATUS current
			DESCRIPTION
				"Topology address of the corresponding POI module to which the POI path belongs to.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiPathThresholdRangeEntry 1 }
		
		-- 1.3.6.1.4.1.331.1.2.1.6.1.1.2.6.1.2
		poiPathThresholdRangeIndexRef OBJECT-TYPE
			SYNTAX PositiveIntegerButNotZero
			MAX-ACCESS read-only
			STATUS current
			DESCRIPTION
				"Referenced POI path index."
			::= { poiPathThresholdRangeEntry 2 }
		
		-- 1.3.6.1.4.1.331.1.2.1.6.1.1.2.6.1.3
		poiPathThresholdRangeAttenuation OBJECT-TYPE
			SYNTAX OCTET STRING
			MAX-ACCESS read-only
			STATUS current
			DESCRIPTION
				"Range for the poiPathPowerAttenuation value for the referenced POI type resp. POI path type.
				
				Comma separated string, syntax is 
				'<minValue>,<maxValue>,<step>' with
				<minValue>: Minimum value, string representation of a float value
				<maxValue>: Maximum value, string representation of a float value
				<step>: Step value, string representation of a float value"
			::= { poiPathThresholdRangeEntry 3 }
		
		-- 1.3.6.1.4.1.331.1.2.1.6.1.1.2.6.1.4
		poiPathThresholdRangeHipAr OBJECT-TYPE
			SYNTAX OCTET STRING
			MAX-ACCESS read-only
			STATUS current
			DESCRIPTION
				"Range for the poiPathThresholdHipAr value for the referenced POI type resp. POI path type.
				
				Comma separated string, syntax is 
				'<minValue>,<maxValue>,<step>' with
				<minValue>: Variable for actual minimum value, string representation of a float value
				<maxValue>: Variable for actual maximum value, string representation of a float value
				<step>: Variable for actual step value, string representation of a float value
				
				Note well:
				- 'notAvailable' may be responded in case the value is temporary not available (try later).
				- 'notSupported' indicates that the object is not supported by the referenced POI type resp. POI path type."
			::= { poiPathThresholdRangeEntry 4 }
		
		-- 1.3.6.1.4.1.331.1.2.1.6.1.1.2.6.1.5
		poiPathThresholdRangeALC OBJECT-TYPE
			SYNTAX OCTET STRING
			MAX-ACCESS read-only
			STATUS current
			DESCRIPTION
				"Range for the poiPathThresholdALC value for the referenced POI type resp. POI path type.
				
				Comma separated string, syntax is 
				'<minValue>,<maxValue>,<step>' with
				<minValue>: Variable for actual minimum value, string representation of a float value
				<maxValue>: Variable for actual maximum value, string representation of a float value
				<step>: Variable for actual step value, string representation of a float value
				
				Note well:
				- 'notAvailable' may be responded in case the value is temporary not available (try later).
				- 'notSupported' indicates that the object is not supported by the referenced POI type resp. POI path type."
			::= { poiPathThresholdRangeEntry 5 }
		
		-- 1.3.6.1.4.1.331.1.2.1.6.1.1.2.6.1.6
		poiPathThresholdRangeLipAr OBJECT-TYPE
			SYNTAX OCTET STRING
			MAX-ACCESS read-only
			STATUS current
			DESCRIPTION
				"Range for the poiPathThresholdLipAr value for the referenced POI type resp. POI path type.
				
				Comma separated string, syntax is 
				'<minValue>,<maxValue>,<step>' with
				<minValue>: Variable for actual minimum value, string representation of a float value
				<maxValue>: Variable for actual maximum value, string representation of a float value
				<step>: Variable for actual step value, string representation of a float value
				
				Note well:
				- 'notAvailable' may be responded in case the value is temporary not available (try later).
				- 'notSupported' indicates that the object is not supported by the referenced POI type resp. POI path type."
			::= { poiPathThresholdRangeEntry 6 }
		
		-- 1.3.6.1.4.1.331.1.2.1.6.1.1.2.6.1.7
		poiPathThresholdRangeLipAc OBJECT-TYPE
			SYNTAX OCTET STRING
			MAX-ACCESS read-only
			STATUS current
			DESCRIPTION
				"Range for the poiPathThresholdLipAc value for the referenced POI type resp. POI path type.
				
				Comma separated string, syntax is 
				'<minValue>,<maxValue>,<step>' with
				<minValue>: Variable for actual minimum value, string representation of a float value
				<maxValue>: Variable for actual maximum value, string representation of a float value
				<step>: Variable for actual step value, string representation of a float value
				
				Note well:
				- 'notAvailable' may be responded in case the value is temporary not available (try later).
				- 'notSupported' indicates that the object is not supported by the referenced POI type resp. POI path type."
			::= { poiPathThresholdRangeEntry 7 }
		
		-- 1.3.6.1.4.1.331.1.2.1.6.1.1.2.7
		poiPathAlarmSuppressionTable OBJECT-TYPE
			SYNTAX SEQUENCE OF PoiPathAlarmSuppressionEntry
			MAX-ACCESS not-accessible
			STATUS current
			DESCRIPTION
				"Description."
			::= { ionmLocal 7 }
		
		-- 1.3.6.1.4.1.331.1.2.1.6.1.1.2.7.1
		poiPathAlarmSuppressionEntry OBJECT-TYPE
			SYNTAX PoiPathAlarmSuppressionEntry
			MAX-ACCESS not-accessible
			STATUS current
			DESCRIPTION
				"Description."
			INDEX { poiPathAlarmSuppressionPoiCTA, poiPathAlarmSuppressionIndexRef }
			::= { poiPathAlarmSuppressionTable 1 }
		
		PoiPathAlarmSuppressionEntry ::=
			SEQUENCE { 
				poiPathAlarmSuppressionPoiCTA
					CTA,
				poiPathAlarmSuppressionIndexRef
					PositiveIntegerButNotZero,
				poiPathAlarmSuppressionALC
					BoolOrNotSupportedOrNotAvailable,
				poiPathAlarmSuppressionHip
					BoolOrNotSupportedOrNotAvailable,
				poiPathAlarmSuppressionLip
					BoolOrNotSupportedOrNotAvailable
			 }

		-- 1.3.6.1.4.1.331.1.2.1.6.1.1.2.7.1.1
		poiPathAlarmSuppressionPoiCTA OBJECT-TYPE
			SYNTAX CTA
			MAX-ACCESS read-only
			STATUS current
			DESCRIPTION
				"Topology address of the corresponding POI module to which the POI path belongs to.
				
				The corresponding POI subrack and slot numbers have to be calculated out of the POI address. 
				The POI address is the integer number following the equal sign ('=') of the CTA string. 
				
				POI-SR = ( (POI_address - 1) / 8 ) + 1 where '/' represents a integer division with remainder
				POI-Slot = ( (POI_address - 1) % 8 ) + 1 where '%' represents a modulo operation
				
				E.g. 
				CTA = 'POI=1'  is located in POI-SR 1  slot 1
				CTA = 'POI=64' is located in POI-SR 8  slot 8
				CTA = 'POI=65' is located in POI-SR 9  slot 1
				CTA = 'POI=80' is located in POI-SR 10 slot 8
				CTA = 'POI=81' is located in POI-SR 11 slot 1"
			::= { poiPathAlarmSuppressionEntry 1 }
		
		-- 1.3.6.1.4.1.331.1.2.1.6.1.1.2.7.1.2
		poiPathAlarmSuppressionIndexRef OBJECT-TYPE
			SYNTAX PositiveIntegerButNotZero
			MAX-ACCESS read-only
			STATUS current
			DESCRIPTION
				"Referenced POI path index."
			::= { poiPathAlarmSuppressionEntry 2 }
		
		-- 1.3.6.1.4.1.331.1.2.1.6.1.1.2.7.1.3
		poiPathAlarmSuppressionALC OBJECT-TYPE
			SYNTAX BoolOrNotSupportedOrNotAvailable
			MAX-ACCESS read-write
			STATUS current
			DESCRIPTION
				"ALC Alarm Suppression.
				
				Note well:
				- notAvailable(-1) may be responded in case the value is temporary not available (try later).
				- notSupported(0) indicates that the object is not supported by the referenced POI type resp. POI path type.
				- Allowed values for SET are just true(1) or false(2)"
			::= { poiPathAlarmSuppressionEntry 3 }
		
		-- 1.3.6.1.4.1.331.1.2.1.6.1.1.2.7.1.4
		poiPathAlarmSuppressionHip OBJECT-TYPE
			SYNTAX BoolOrNotSupportedOrNotAvailable
			MAX-ACCESS read-write
			STATUS current
			DESCRIPTION
				"High Input Power Alarm Suppression.
				
				Note well:
				- notAvailable(-1) may be responded in case the value is temporary not available (try later).
				- notSupported(0) indicates that the object is not supported by the referenced POI type resp. POI path type.
				- Allowed values for SET are just true(1) or false(2)"
			::= { poiPathAlarmSuppressionEntry 4 }
		
		-- 1.3.6.1.4.1.331.1.2.1.6.1.1.2.7.1.5
		poiPathAlarmSuppressionLip OBJECT-TYPE
			SYNTAX BoolOrNotSupportedOrNotAvailable
			MAX-ACCESS read-write
			STATUS current
			DESCRIPTION
				"Low Input Power Alarm Suppression.
				
				Note well:
				- notAvailable(-1) may be responded in case the value is temporary not available (try later).
				- notSupported(0) indicates that the object is not supported by the referenced POI type resp. POI path type.
				- Allowed values for SET are just true(1) or false(2)"
			::= { poiPathAlarmSuppressionEntry 5 }
		
		-- 1.3.6.1.4.1.331.1.2.1.6.1.1.2.8
		poiIfcTable OBJECT-TYPE
			SYNTAX SEQUENCE OF PoiIfcEntry
			MAX-ACCESS not-accessible
			STATUS current
			DESCRIPTION
				"This table lists all IFC modules."
			::= { ionmLocal 8 }
		
		-- 1.3.6.1.4.1.331.1.2.1.6.1.1.2.8.1
		poiIfcEntry OBJECT-TYPE
			SYNTAX PoiIfcEntry
			MAX-ACCESS not-accessible
			STATUS current
			DESCRIPTION
				"Description."
			INDEX { poiIfcCTA }
			::= { poiIfcTable 1 }
		
		PoiIfcEntry ::=
			SEQUENCE { 
				poiIfcCTA
					CTA,
				poiIfcTemp
					Integer32
			 }

		-- 1.3.6.1.4.1.331.1.2.1.6.1.1.2.8.1.1
		poiIfcCTA OBJECT-TYPE
			SYNTAX CTA
			MAX-ACCESS read-only
			STATUS current
			DESCRIPTION
				"Topology address of the IFC module.
				
				The POI subrack number corresponds with the IFC address. 
				The IFC address is the integer number following the equal sign ('=') of the CTA string. 
				
				E.g. 
				CTA = 'IFC=1'  is located in POI-SR 1
				CTA = 'IFC=8'  is located in POI-SR 8
				CTA = 'IFC=16' is located in POI-SR 16"
			::= { poiIfcEntry 1 }
		
		-- 1.3.6.1.4.1.331.1.2.1.6.1.1.2.8.1.2
		poiIfcTemp OBJECT-TYPE
			SYNTAX Integer32
			MAX-ACCESS read-only
			STATUS current
			DESCRIPTION
				"IFC module temperature in degree Celsius.
				
				Note well:
				- MIN(Integer32) may be responded in case the value is temporary not available (try later).
				- MAX(Integer32) indicates that the object is not supported by the referenced IFC."
			::= { poiIfcEntry 2 }
		
		-- 1.3.6.1.4.1.331.1.2.1.6.1.1.3
		ionmRemote OBJECT-IDENTITY
			STATUS current
			DESCRIPTION 
				"Description."
			::= { ionmConfiguration 3 }
		
		-- 1.3.6.1.4.1.331.1.2.1.6.1.1.3.1
		ruTable OBJECT-TYPE
			SYNTAX SEQUENCE OF RuEntry
			MAX-ACCESS not-accessible
			STATUS current
			DESCRIPTION
				"Description."
			::= { ionmRemote 1 }
		
		-- 1.3.6.1.4.1.331.1.2.1.6.1.1.3.1.1
		ruEntry OBJECT-TYPE
			SYNTAX RuEntry
			MAX-ACCESS not-accessible
			STATUS current
			DESCRIPTION
				"Description."
			INDEX { ruCTA }
			::= { ruTable 1 }
		
		RuEntry ::=
			SEQUENCE { 
				ruCTA
					CTA,
				ruReboot
					TruthValue,
				ruPsuPowerCycle
					TruthValue,
				ruAutoLevellingOpticalLossUL
					OCTET STRING,
				ruAutoLevellingOpticalLossDL
					OCTET STRING,
				ruTempOperating
					Integer32,
				ruTempOptic
					OCTET STRING,
				ruTempPSU1
					OCTET STRING,
				ruTempPSU2
					OCTET STRING,
				ruGainReductionMonitoringActive
					TruthValue,
				ruGainReductionMonitoringInterval
					Integer32,
				ruPsuWatchdogActive
					TruthValue,
				ruPsuWatchdogInterval
					Integer32
			 }

		-- 1.3.6.1.4.1.331.1.2.1.6.1.1.3.1.1.1
		ruCTA OBJECT-TYPE
			SYNTAX CTA
			MAX-ACCESS read-only
			STATUS current
			DESCRIPTION
				"Description."
			::= { ruEntry 1 }
		
		-- 1.3.6.1.4.1.331.1.2.1.6.1.1.3.1.1.2
		ruReboot OBJECT-TYPE
			SYNTAX TruthValue
			MAX-ACCESS read-write
			STATUS current
			DESCRIPTION
				"Description."
			::= { ruEntry 2 }
		
		-- 1.3.6.1.4.1.331.1.2.1.6.1.1.3.1.1.3
		ruPsuPowerCycle OBJECT-TYPE
			SYNTAX TruthValue
			MAX-ACCESS read-write
			STATUS current
			DESCRIPTION
				"Description."
			::= { ruEntry 3 }
		
		-- 1.3.6.1.4.1.331.1.2.1.6.1.1.3.1.1.4
		ruAutoLevellingOpticalLossUL OBJECT-TYPE
			SYNTAX OCTET STRING
			MAX-ACCESS read-only
			STATUS current
			DESCRIPTION
				"String representation of float value."
			::= { ruEntry 4 }
		
		-- 1.3.6.1.4.1.331.1.2.1.6.1.1.3.1.1.5
		ruAutoLevellingOpticalLossDL OBJECT-TYPE
			SYNTAX OCTET STRING
			MAX-ACCESS read-only
			STATUS current
			DESCRIPTION
				"String representation of float value."
			::= { ruEntry 5 }
		
		-- 1.3.6.1.4.1.331.1.2.1.6.1.1.3.1.1.6
		ruTempOperating OBJECT-TYPE
			SYNTAX Integer32
			MAX-ACCESS read-write
			STATUS current
			DESCRIPTION
				"Description."
			::= { ruEntry 6 }
		
		-- 1.3.6.1.4.1.331.1.2.1.6.1.1.3.1.1.7
		ruTempOptic OBJECT-TYPE
			SYNTAX OCTET STRING
			MAX-ACCESS read-only
			STATUS current
			DESCRIPTION
				"String representation of float value."
			::= { ruEntry 7 }
		
		-- 1.3.6.1.4.1.331.1.2.1.6.1.1.3.1.1.8
		ruTempPSU1 OBJECT-TYPE
			SYNTAX OCTET STRING
			MAX-ACCESS read-only
			STATUS current
			DESCRIPTION
				"String representation of float value."
			::= { ruEntry 8 }
		
		-- 1.3.6.1.4.1.331.1.2.1.6.1.1.3.1.1.9
		ruTempPSU2 OBJECT-TYPE
			SYNTAX OCTET STRING
			MAX-ACCESS read-only
			STATUS current
			DESCRIPTION
				"String representation of float value."
			::= { ruEntry 9 }
		
		-- 1.3.6.1.4.1.331.1.2.1.6.1.1.3.1.1.10
		ruGainReductionMonitoringActive OBJECT-TYPE
			SYNTAX TruthValue
			MAX-ACCESS read-write
			STATUS current
			DESCRIPTION
				"Description."
			::= { ruEntry 10 }
		
		-- 1.3.6.1.4.1.331.1.2.1.6.1.1.3.1.1.11
		ruGainReductionMonitoringInterval OBJECT-TYPE
			SYNTAX Integer32
			MAX-ACCESS read-write
			STATUS current
			DESCRIPTION
				"Description."
			::= { ruEntry 11 }
		
		-- 1.3.6.1.4.1.331.1.2.1.6.1.1.3.1.1.12
		ruPsuWatchdogActive OBJECT-TYPE
			SYNTAX TruthValue
			MAX-ACCESS read-write
			STATUS current
			DESCRIPTION
				"Description."
			::= { ruEntry 12 }
		
		-- 1.3.6.1.4.1.331.1.2.1.6.1.1.3.1.1.13
		ruPsuWatchdogInterval OBJECT-TYPE
			SYNTAX Integer32
			MAX-ACCESS read-write
			STATUS current
			DESCRIPTION
				"Description."
			::= { ruEntry 13 }
		
		-- 1.3.6.1.4.1.331.1.2.1.6.1.1.3.2
		euTable OBJECT-TYPE
			SYNTAX SEQUENCE OF EuEntry
			MAX-ACCESS not-accessible
			STATUS current
			DESCRIPTION
				"Description."
			::= { ionmRemote 2 }
		
		-- 1.3.6.1.4.1.331.1.2.1.6.1.1.3.2.1
		euEntry OBJECT-TYPE
			SYNTAX EuEntry
			MAX-ACCESS not-accessible
			STATUS current
			DESCRIPTION
				"Description."
			INDEX { euCTA }
			::= { euTable 1 }
		
		EuEntry ::=
			SEQUENCE { 
				euCTA
					CTA,
				euReboot
					TruthValue,
				euPsuPowerCycle
					TruthValue,
				euTempOperating
					Integer32,
				euTempPSU1
					OCTET STRING,
				euTempPSU2
					OCTET STRING,
				euPsuWatchdogActive
					TruthValue,
				euPsuWatchdogInterval
					Integer32
			 }

		-- 1.3.6.1.4.1.331.1.2.1.6.1.1.3.2.1.1
		euCTA OBJECT-TYPE
			SYNTAX CTA
			MAX-ACCESS read-only
			STATUS current
			DESCRIPTION
				"Description."
			::= { euEntry 1 }
		
		-- 1.3.6.1.4.1.331.1.2.1.6.1.1.3.2.1.2
		euReboot OBJECT-TYPE
			SYNTAX TruthValue
			MAX-ACCESS read-write
			STATUS current
			DESCRIPTION
				"Description."
			::= { euEntry 2 }
		
		-- 1.3.6.1.4.1.331.1.2.1.6.1.1.3.2.1.3
		euPsuPowerCycle OBJECT-TYPE
			SYNTAX TruthValue
			MAX-ACCESS read-write
			STATUS current
			DESCRIPTION
				"Description."
			::= { euEntry 3 }
		
		-- 1.3.6.1.4.1.331.1.2.1.6.1.1.3.2.1.4
		euTempOperating OBJECT-TYPE
			SYNTAX Integer32
			MAX-ACCESS read-write
			STATUS current
			DESCRIPTION
				"Description."
			::= { euEntry 4 }
		
		-- 1.3.6.1.4.1.331.1.2.1.6.1.1.3.2.1.5
		euTempPSU1 OBJECT-TYPE
			SYNTAX OCTET STRING
			MAX-ACCESS read-only
			STATUS current
			DESCRIPTION
				"String representation of float value."
			::= { euEntry 5 }
		
		-- 1.3.6.1.4.1.331.1.2.1.6.1.1.3.2.1.6
		euTempPSU2 OBJECT-TYPE
			SYNTAX OCTET STRING
			MAX-ACCESS read-only
			STATUS current
			DESCRIPTION
				"String representation of float value."
			::= { euEntry 6 }
		
		-- 1.3.6.1.4.1.331.1.2.1.6.1.1.3.2.1.7
		euPsuWatchdogActive OBJECT-TYPE
			SYNTAX TruthValue
			MAX-ACCESS read-write
			STATUS current
			DESCRIPTION
				"Description."
			::= { euEntry 7 }
		
		-- 1.3.6.1.4.1.331.1.2.1.6.1.1.3.2.1.8
		euPsuWatchdogInterval OBJECT-TYPE
			SYNTAX Integer32
			MAX-ACCESS read-write
			STATUS current
			DESCRIPTION
				"Description."
			::= { euEntry 8 }
		
		-- 1.3.6.1.4.1.331.1.2.1.6.1.1.3.3
		dlpaTable OBJECT-TYPE
			SYNTAX SEQUENCE OF DlpaEntry
			MAX-ACCESS not-accessible
			STATUS current
			DESCRIPTION
				"Description."
			::= { ionmRemote 3 }
		
		-- 1.3.6.1.4.1.331.1.2.1.6.1.1.3.3.1
		dlpaEntry OBJECT-TYPE
			SYNTAX DlpaEntry
			MAX-ACCESS not-accessible
			STATUS current
			DESCRIPTION
				"Description."
			INDEX { dlpaContainingUnitCTA, dlpaNo }
			::= { dlpaTable 1 }
		
		DlpaEntry ::=
			SEQUENCE { 
				dlpaContainingUnitCTA
					CTA,
				dlpaNo
					PositiveIntegerButNotZero,
				dlpaReset
					TruthValue,
				dlpaActive
					TruthValue,
				dlpaFrequency
					OCTET STRING,
				dlpaOutputPower
					OCTET STRING,
				dlpaTemp
					OCTET STRING,
				dlpaLowRmsEnabled
					TruthValue,
				dlpaLowRmsThreshold
					OCTET STRING,
				dlpaLowRmsHysteresis
					OCTET STRING
			 }

		-- 1.3.6.1.4.1.331.1.2.1.6.1.1.3.3.1.1
		dlpaContainingUnitCTA OBJECT-TYPE
			SYNTAX CTA
			MAX-ACCESS read-only
			STATUS current
			DESCRIPTION
				"Description."
			::= { dlpaEntry 1 }
		
		-- 1.3.6.1.4.1.331.1.2.1.6.1.1.3.3.1.2
		dlpaNo OBJECT-TYPE
			SYNTAX PositiveIntegerButNotZero
			MAX-ACCESS read-only
			STATUS current
			DESCRIPTION
				"Description."
			::= { dlpaEntry 2 }
		
		-- 1.3.6.1.4.1.331.1.2.1.6.1.1.3.3.1.3
		dlpaReset OBJECT-TYPE
			SYNTAX TruthValue
			MAX-ACCESS read-write
			STATUS current
			DESCRIPTION
				"Description."
			::= { dlpaEntry 3 }
		
		-- 1.3.6.1.4.1.331.1.2.1.6.1.1.3.3.1.4
		dlpaActive OBJECT-TYPE
			SYNTAX TruthValue
			MAX-ACCESS read-write
			STATUS current
			DESCRIPTION
				"Description."
			::= { dlpaEntry 4 }
		
		-- 1.3.6.1.4.1.331.1.2.1.6.1.1.3.3.1.5
		dlpaFrequency OBJECT-TYPE
			SYNTAX OCTET STRING
			MAX-ACCESS read-only
			STATUS current
			DESCRIPTION
				"Description."
			::= { dlpaEntry 5 }
		
		-- 1.3.6.1.4.1.331.1.2.1.6.1.1.3.3.1.6
		dlpaOutputPower OBJECT-TYPE
			SYNTAX OCTET STRING
			MAX-ACCESS read-only
			STATUS current
			DESCRIPTION
				"String representation of float value."
			::= { dlpaEntry 6 }
		
		-- 1.3.6.1.4.1.331.1.2.1.6.1.1.3.3.1.7
		dlpaTemp OBJECT-TYPE
			SYNTAX OCTET STRING
			MAX-ACCESS read-only
			STATUS current
			DESCRIPTION
				"String representation of float value."
			::= { dlpaEntry 7 }
		
		-- 1.3.6.1.4.1.331.1.2.1.6.1.1.3.3.1.8
		dlpaLowRmsEnabled OBJECT-TYPE
			SYNTAX TruthValue
			MAX-ACCESS read-write
			STATUS current
			DESCRIPTION
				"Description."
			::= { dlpaEntry 8 }
		
		-- 1.3.6.1.4.1.331.1.2.1.6.1.1.3.3.1.9
		dlpaLowRmsThreshold OBJECT-TYPE
			SYNTAX OCTET STRING
			MAX-ACCESS read-write
			STATUS current
			DESCRIPTION
				"String representation of float value."
			::= { dlpaEntry 9 }
		
		-- 1.3.6.1.4.1.331.1.2.1.6.1.1.3.3.1.10
		dlpaLowRmsHysteresis OBJECT-TYPE
			SYNTAX OCTET STRING
			MAX-ACCESS read-write
			STATUS current
			DESCRIPTION
				"String representation of float value."
			::= { dlpaEntry 10 }
		
		-- 1.3.6.1.4.1.331.1.2.1.6.1.1.4
		ionmConformance OBJECT-IDENTITY
			STATUS current
			DESCRIPTION 
				"Description."
			::= { ionmConfiguration 4 }
		
		-- 1.3.6.1.4.1.331.1.2.1.6.1.1.4.1
		ionmConfigurationGroup OBJECT-GROUP
			OBJECTS { muOtrxCTA, muOtrxReboot, muOtrxTempOptic, ruCTA, ruReboot, 
				ruPsuPowerCycle, ruAutoLevellingOpticalLossUL, ruAutoLevellingOpticalLossDL, ruTempOperating, ruTempOptic, 
				ruTempPSU1, ruTempPSU2, ruGainReductionMonitoringActive, ruGainReductionMonitoringInterval, ruPsuWatchdogActive, 
				ruPsuWatchdogInterval, euCTA, euReboot, euPsuPowerCycle, euTempOperating, 
				euTempPSU1, euTempPSU2, euPsuWatchdogActive, euPsuWatchdogInterval, dlpaContainingUnitCTA, 
				dlpaNo, dlpaReset, dlpaActive, dlpaFrequency, dlpaOutputPower, 
				dlpaTemp, dlpaLowRmsEnabled, dlpaLowRmsThreshold, dlpaLowRmsHysteresis, poiCTA, 
				poiName, poiLocation, poiSectorID, poiFrequency, poiStandard, 
				poiUserAssignment, poiTemp, poiPathPoiCTA, poiPathIndex, poiPathLabel, 
				poiPathIsActive, poiPathAlcEnabled, poiIfcCTA, poiIfcTemp, customMIB, 
				accountGroupId, accountGroupRole, accountGroupName, accountGroupIdref, accountId, 
				accountName, poiPathPowerPoiCTA, poiPathPowerIndexRef, poiPathPowerInput, poiPathPowerAttenuation, 
				poiPathPowerOutput, poiPathThresholdPoiCTA, poiPathThresholdIndexRef, poiPathThresholdHipAr, poiPathThresholdALC, 
				poiPathThresholdLipAr, poiPathThresholdLipAc, poiPathThresholdRangePoiCTA, poiPathThresholdRangeIndexRef, poiPathThresholdRangeAttenuation, 
				poiPathThresholdRangeHipAr, poiPathThresholdRangeALC, poiPathThresholdRangeLipAr, poiPathThresholdRangeLipAc, poiPathAlarmSuppressionPoiCTA, 
				poiPathAlarmSuppressionIndexRef, poiPathAlarmSuppressionALC, poiPathAlarmSuppressionHip, poiPathAlarmSuppressionLip, accountPwNew, 
				accountPwAct, nwSwUpdateMode, nwSwUpdateExclusiveTask, nwSwUpdateState, nwSwSubComponentCTA, 
				nwSwSubComponent, nwSwComponentActVersion, nwSwComponentNewVersion, nwSwComponentFilename, nwSwSelect4Update, 
				nwSwResultOk, nwSwResultString, nwSwSelectAll4Update, nwSwCurrentInProgress, nwSwCurrentPercentage, 
				nwSwOverallPercentage, nwSwOverallResultOk, nwSwOverallResultString }
			STATUS current
			DESCRIPTION 
				"Description."
			::= { ionmConformance 1 }
		
	
	END

--
-- IONM-MIB.mib
--
